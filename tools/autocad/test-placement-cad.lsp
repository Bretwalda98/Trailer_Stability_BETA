; Executed only inside an isolated test drawing by test-placement-cad.ps1.
(defun qa:require (condition description)
  (if (not condition) (progn (setq qa:ok nil) (setq qa:failures (cons description qa:failures))))
  condition)
(defun qa:placement-case (name / data attrs result entities layerData record vertices origin actual expected counter deltas)
  (setq data (sartd:v120-read-compact (strcat qa:fixture "/" name ".sartd")))
  (qa:require (and data (= (sartd:g 'cad-version data) 2)
    (= (length (sartd:g 'cad-beds data)) 3) (= (length (sartd:g 'cad-deck-ppus data)) 1)
    (= (sartd:g 'total-powerpacks data) 2) (< (abs (- (sartd:g 'total-ppu-weight data) 12.4)) 0.000001)) "Parsed bed/PPU counts or mass mismatch")
  (if data
    (progn
      (setq attrs (sartd:attr-map data))
      (qa:require (= (cdr (assoc "TOTALNUMBEROFPOWERPACKS" attrs)) "2") "PPU count annotation")
      (qa:require (= (cdr (assoc "NEUTRALGROUP1" attrs)) (sartd:v121-group-fixed data 1 'neutral-pressure 0)) "G1 pressure annotation")
      (if (= name "FOUR_POINT")
        (qa:require (= (cdr (assoc "NEUTRALGROUP4" attrs)) (sartd:v121-group-fixed data 4 'neutral-pressure 0)) "G4 pressure annotation"))
      (if qa:draw
        (progn
          (setq sartd:*v118-run-source-label* "CAD v2 isolated test")
          (setq result (vl-catch-all-apply 'sartd:v118-run-model-from-data (list data)))
          (qa:require (and result (not (vl-catch-all-error-p result))) "ModelSpace drawing failed")
          (setq entities (ssget "_X" '((8 . "SARTD-PPU"))))
          (qa:require (and entities (>= (sslength entities) 8)) "Missing PPU plan/elevation entities")
          (if entities (setq qa:count (+ qa:count (sslength entities))))
          ; Selection-set order is unspecified: check all projected longitudinal edges.
          (setq entities (ssget "_X" '((0 . "LWPOLYLINE") (8 . "SARTD-BED"))))
          (qa:require (and entities (= (sslength entities) 3)) "BED path count mismatch")
          (if entities
            (progn
              (setq counter 0 deltas nil)
              (repeat (sslength entities)
                (setq vertices (mapcar 'cdr (vl-remove-if-not '(lambda (p) (= (car p) 10)) (entget (ssname entities counter)))))
                (setq deltas (cons (- (cadr (cadr vertices)) (cadr (car vertices))) deltas) counter (1+ counter)))
              (qa:require (< (abs (- (apply 'max deltas) (* 8400.0 (sin (* pi (/ 10.0 180.0)))))) 0.001) "Positive BED rotation mismatch")
              (qa:require (< (abs (- (apply 'min deltas) (* 7000.0 (sin (* pi (/ -5.0 180.0)))))) 0.001) "Negative BED rotation mismatch")))
          (setq sartd:*v118-run-data* data)
          (defun sartd:v38-select-paper-template () (setq sartd:*paper-template-label* "Isolated template test") (if (= qa:name "THREE_POINT") "1-1" "2-2"))
          (setq result (vl-catch-all-apply 'sartd:v118-run-paper-from-data (list data)))
          (qa:require (and result (not (vl-catch-all-error-p result))) "PaperSpace sheet and attributes failed")
          (setq result (vl-catch-all-apply 'sartd:v118-run-border-from-data (list data)))
          (qa:require (and result (not (vl-catch-all-error-p result))) "Border attributes failed")))
      (setq qa:cases (1+ qa:cases)))))

(setq qa:ok T qa:failures nil qa:cases 0 qa:count 0)
(foreach qa:name '("THREE_POINT" "FOUR_POINT")
  (setq qa:r (vl-catch-all-apply 'qa:placement-case (list qa:name)))
  (if (vl-catch-all-error-p qa:r) (qa:require nil (vl-catch-all-error-message qa:r))))
(qa:require (= qa:cases 2) "Both hydraulic fixtures must complete")
(foreach qa:name '("wrong-version" "wrong-units" "missing-geometry" "bad-coordinate" "bad-ppu")
  (qa:require (null (sartd:v120-read-compact (strcat qa:fixture "/" qa:name ".sartd"))) (strcat "Accepted malformed " qa:name)))
(qa:require (sartd:v120-read-compact qa:legacy) "Legacy v1 regression")
(setq qa:file (open qa:marker "w"))
(write-line (if qa:ok "PLACEMENT-CAD-PASS" "PLACEMENT-CAD-FAIL") qa:file)
(write-line (strcat "CASES=" (itoa qa:cases) " PPU-ENTITIES=" (itoa qa:count)) qa:file)
(foreach qa:failure qa:failures (write-line qa:failure qa:file))
(close qa:file)
(princ)
