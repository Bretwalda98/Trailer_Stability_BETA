; SARTD-CAD v2 / package v1.23. Data-only import: never READ or EVAL file content.
(vl-load-com)

(defun sartd:v123-number (s / n)
  (if (and (= (type s) 'STR) (/= s "")
           (vl-every '(lambda (c) (member c '(43 45 46 48 49 50 51 52 53 54 55 56 57))) (vl-string->list s))
           (setq n (distof s 2)) (< (abs n) 1e12)) n nil))

(defun sartd:v123-points (field / result good pair parts)
  (setq result nil good T)
  (foreach pair (sartd:v120-split field ";")
    (setq parts (sartd:v120-split pair ","))
    (if (and (= (length parts) 2) (vl-every 'sartd:v123-number parts))
      (setq result (cons (mapcar 'sartd:v123-number parts) result))
      (setq good nil)))
  (if (and good (>= (length result) 2) (<= (length result) 10000)) (reverse result) nil))

(defun sartd:v123-validate (beds ppus graphics trailers ending boundary mode / errors r views ids index nums)
  (setq errors nil views nil ids nil)
  (if (or (/= (sartd:v120-integer ending 1 -1) (length trailers))
          (/= (sartd:v120-integer ending 2 -1) (apply '+ (mapcar '(lambda (tr) (cdr (assoc 'axles tr))) trailers)))
          (/= (sartd:v120-integer ending 5 -1) (length boundary))
          (/= (sartd:v120-integer ending 6 -1) (length beds))
          (/= (sartd:v120-integer ending 7 -1) (length ppus))
          (/= (sartd:v120-integer ending 8 -1) (length graphics)))
    (setq errors (cons "CAD v2 END counts do not match the file records." errors)))
  (if (/= (length boundary) (if (= mode "FOUR_POINT") 4 3))
    (setq errors (cons "CAD v2 requires the authoritative three- or four-point boundary." errors)))
  (foreach r beds
    (if (or (/= (length r) 9) (= (nth 1 r) "") (member (nth 1 r) ids)
            (not (vl-every 'sartd:v123-number (cddr r))))
      (setq errors (cons "Invalid or duplicate BED record." errors))
      (progn
        (setq ids (cons (nth 1 r) ids) index (sartd:v120-integer r 2 0))
        (if (or (< index 1) (> index (length trailers)) (not (member (sartd:v120-number r 3 0) '(4.0 5.0 6.0)))
                (> (abs (sartd:v120-number r 6 0)) 45) (<= (sartd:v120-number r 7 0) 0) (<= (sartd:v120-number r 8 0) 0))
          (setq errors (cons "BED host, size or rotation is invalid." errors))))))
  (setq ids nil)
  (foreach r ppus
    (setq nums (if (>= (length r) 15) (list (nth 2 r) (nth 3 r) (nth 4 r) (nth 5 r) (nth 6 r) (nth 7 r) (nth 8 r) (nth 9 r) (nth 10 r) (nth 12 r)) nil))
    (if (or (/= (length r) 15) (= (nth 1 r) "") (member (nth 1 r) ids) (not nums) (not (vl-every 'sartd:v123-number nums)))
      (setq errors (cons "Invalid or duplicate DECKPPU record." errors))
      (progn
        (setq ids (cons (nth 1 r) ids) index (sartd:v120-integer r 2 0))
        (if (or (< index 1) (> index (length trailers)) (not (= (nth 11 r) "1"))
                (<= (sartd:v120-number r 6 0) 0) (<= (sartd:v120-number r 7 0) 0) (<= (sartd:v120-number r 8 0) 0) (<= (sartd:v120-number r 9 0) 0)
                (< (sartd:v120-number r 10 0) 0) (> (sartd:v120-number r 10 0) (sartd:v120-number r 8 0)))
          (setq errors (cons "DECKPPU must have a valid host, dimensions, mass, COG and securing confirmation." errors))))))
  (if (or (null graphics) (> (length graphics) 50000)) (setq errors (cons "CAD v2 geometry is missing or too large." errors)))
  (foreach r graphics
    (if (or (not (member (nth 1 r) '("PLAN" "SIDE" "END")))
            (not (member (nth 2 r) '("SARTD-LOAD" "SARTD-PACKING" "SARTD-INACTIVE" "SARTD-TRAILER" "SARTD-TEXT" "SARTD-PPU" "SARTD-BED" "SARTD-COG" "SARTD-STABILITY" "SARTD-HYD-G1" "SARTD-HYD-G2" "SARTD-HYD-G3" "SARTD-HYD-G4"))))
      (setq errors (cons "Invalid geometry view or layer." errors)))
    (setq views (sartd:v120-add-unique (nth 1 r) views))
    (if (= (car r) "VIEWPATH")
      (if (or (/= (length r) 4) (not (sartd:v123-points (nth 3 r)))) (setq errors (cons "Invalid VIEWPATH coordinates." errors)))
      (if (or (/= (length r) 7) (not (vl-every 'sartd:v123-number (list (nth 3 r) (nth 4 r) (nth 5 r)))) (<= (sartd:v120-number r 5 0) 0))
        (setq errors (cons "Invalid VIEWTEXT coordinates or height." errors)))))
  (if (/= (length views) 3) (setq errors (cons "CAD v2 must include PLAN, SIDE and END geometry." errors)))
  errors)

(defun sartd:v123-layer (name / layers obj)
  (setq layers (vla-get-Layers (vla-get-ActiveDocument (vlax-get-acad-object))))
  (if (not (tblsearch "LAYER" name))
    (progn (setq obj (vla-Add layers name)) (vla-put-Color obj (cond ((= name "SARTD-PPU") 3) ((= name "SARTD-INACTIVE") 8) ((= name "SARTD-LOAD") 4) (T 7)))))
  name)

(defun sartd:v123-record-points (r)
  (if (= (car r) "VIEWPATH") (sartd:v123-points (nth 3 r))
    (list (list (sartd:v123-number (nth 3 r)) (sartd:v123-number (nth 4 r))))))

(defun sartd:v123-draw-routed (data base / graphics records view pts p minx miny maxx maxy width height offsets offset x y layer obj ll ur r)
  (if (not (equal (sartd:g 'cad-version data) 2))
    (sartd:draw-arrangement data base)
    (progn
      (setq graphics (sartd:g 'cad-graphics data) offsets nil x (car base) y (cadr base) ll nil ur nil)
      ; Arrange non-overlapping view envelopes in drawing mm, preserving each view's datum.
      (foreach view '("PLAN" "SIDE" "END")
        (setq records (vl-remove-if-not '(lambda (r) (= (nth 1 r) view)) graphics)
              pts (apply 'append (mapcar 'sartd:v123-record-points records))
              minx (apply 'min (mapcar 'car pts)) miny (apply 'min (mapcar 'cadr pts))
              maxx (apply 'max (mapcar 'car pts)) maxy (apply 'max (mapcar 'cadr pts))
              width (- maxx minx) height (- maxy miny) offset (list (- x minx) (- y miny)))
        (setq offsets (cons (cons view offset) offsets))
        (foreach r records
          (setq layer (sartd:v123-layer (nth 2 r))
                pts (mapcar '(lambda (p) (list (+ (car p) (car offset)) (+ (cadr p) (cadr offset)))) (sartd:v123-record-points r)))
          (if (= (car r) "VIEWPATH")
            (setq obj (sartd:add-lwpoly pts layer nil))
            (setq obj (sartd:add-text (nth 6 r) (car pts) (sartd:v123-number (nth 5 r)) layer)))
          (if (not obj) (progn (sartd:v120-log "A CAD v2 entity could not be created.") (exit))))
        (setq y (+ y height (max 5000.0 (* height 0.15)))))
      (sartd:refresh-generated-extents)
      (sartd:v120-log "Resolved bed/PPU plan and orthographic envelopes drawn. Authoritative group tables retained. No geometry was flattened to parallel trains.")
      T)))
(setq sartd:*version* "1.23")
(princ "\nSARTD placement CAD v2 reader/drawing module loaded (v1.23).")
(princ)
